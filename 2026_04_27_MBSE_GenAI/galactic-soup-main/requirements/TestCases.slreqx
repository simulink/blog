# TestCases

## TC-GS-001: Recipe catalog verification (Functional)
Load recipe database; verify >= 8 distinct recipes are selectable via the operator HMI at runtime.
- Rationale: Verifies SR-GS-001

## TC-GS-002: Sustained throughput (Functional)
Run production line for >= 1 h at nominal ingredient supply; verify bowls output >= 200/hr.
- Rationale: Verifies SR-GS-002

## TC-GS-003: Automation level check (Functional)
Observe normal shift operations; verify average automation fraction across components >= 0.8.
- Rationale: Verifies SR-GS-003

## TC-GS-004: Operator-count cap (Functional)
Run a peak-load shift; verify concurrent active operator count <= 5 at all sample points.
- Rationale: Verifies SR-GS-004

## TC-GS-005: Manifest generation (Functional)
Complete a batch; verify a shipping manifest is generated containing batch ID, container count, and destination.
- Rationale: Verifies SR-GS-005

## TC-GS-006: Transport loading time (Functional)
Trigger packaging completion; verify packaged soup is loaded onto transport within 10 min.
- Rationale: Verifies SR-GS-006

## TC-GS-007: Contamination detection (Functional)
Inject contamination in 100 seeded batches; verify at least 99 flagged before sealing (>= 99% sensitivity).
- Rationale: Verifies SR-GS-007

## TC-GS-008: Serving temperature verification (Functional)
Present 20 cooked batches with induced temperature variation; verify only batches with center temperature in 70-95 C pass QC.
- Rationale: Verifies SR-GS-008

## TC-GS-009: 30-day seal life (Functional)
Seal sample containers; apply 30-day vacuum/thermal cycling per interstellar transit profile; verify seal integrity maintained.
- Rationale: Verifies SR-GS-009

## TC-GS-010: Inventory accuracy (Functional)
Audit physical vs. tracked inventory over 30 days of nominal operation; verify discrepancy <= 1%.
- Rationale: Verifies SR-GS-010

## TC-GS-011: Mass budget (analysis) (Functional)
Run runAnalysis(); verify Mass margin >= 0 against the 15000 kg cap.
- Rationale: Verifies SR-GS-011

## TC-GS-012: Power budget (analysis) (Functional)
Run runAnalysis(); verify Power margin >= 0 against the 500 kW cap.
- Rationale: Verifies SR-GS-012

## TC-GS-013: Cost budget (analysis) (Functional)
Run runAnalysis(); verify Cost margin >= 0 against the 2000000 credit cap.
- Rationale: Verifies SR-GS-013

## TC-GS-014: Volume budget (measurement) (Functional)
Measure total enclosed system volume via as-built survey; verify <= 400 m^3. (Not covered by Phase 8 analysis.)
- Rationale: Verifies SR-GS-014

## TC-GS-015: Gravity operating range (Functional)
Perform cooking, packaging, and shipping reference runs at 0.1 g, 1 g, 6 g, and 12 g; verify nominal behavior at each setpoint.
- Rationale: Verifies SR-GS-015

## TC-GS-016: Structural 12 g tolerance (Functional)
Apply sustained 12 g load to structural elements per structural test procedure; verify no permanent deformation post-test.
- Rationale: Verifies SR-GS-016

## TC-GS-017: Concurrent-rocket capacity (Functional)
Dock three rockets simultaneously; verify all three are serviced (loaded or unloaded) without queuing conflicts.
- Rationale: Verifies SR-GS-017

## TC-GS-018: Rocket turnaround (Functional)
Dock a reference rocket at a free pad; verify load-or-unload completes within 20 min of dock-time.
- Rationale: Verifies SR-GS-018

## TC-GS-019: On-site refueling (Functional)
Dock a rocket requiring fuel service; verify onsite refueling completes to nominal fuel level.
- Rationale: Verifies SR-GS-019

## TC-GS-020: Storage zone separation (Functional)
Inspect storage area; verify cold and room-temperature zones are physically and thermally separated and each holds its nominal target temperature.
- Rationale: Verifies SR-GS-020

## TC-GS-021: 72 h ingredient capacity (Functional)
Load ingredients at 72 h nominal consumption rate; verify storage accepts the full volume without overflow or cold-chain violation.
- Rationale: Verifies SR-GS-021

## TC-GS-022: Cooking capacity (Functional)
Operate cooking subsystem at continuous steady state; verify sustained cook rate meets or exceeds the system throughput target.
- Rationale: Verifies SR-GS-022

## TC-GS-023: Internal transfer rate (Functional)
Measure transfer rate from storage to cooking at nominal demand; verify sustained flow meets cooking-demand rate.
- Rationale: Verifies SR-GS-023

## TC-GS-024: Transfer automation fraction (Functional)
Observe internal transfer operations over a nominal shift; verify >= 90% of transfers are automated (no operator assist).
- Rationale: Verifies SR-GS-024

## TC-GS-025: Startup readiness (Functional)
Trigger a cold start from fully-off state; verify system reaches nominal operating throughput within the defined startup period.
- Rationale: Verifies SR-GS-025

## TC-GS-026: Single-fault tolerance (Functional)
Inject a single internal component fault during production; verify no uncontrolled termination (system degrades gracefully or continues).
- Rationale: Verifies SR-GS-026

## TC-GS-027: Production coordination (Functional)
Observe concurrent operations across shifts; verify throughput, safety, and logistical constraints are simultaneously satisfied.
- Rationale: Verifies SR-GS-027

## TC-GS-028: Preparation zone (Functional)
Inspect factory layout; verify a physically-isolated prep zone exists containing chopping and weighing stations. Run prep in isolation; verify sustained prep rate >= 200 bowls/hour equivalent.
- Rationale: Verifies SR-GS-028
